// SysML 2 textual, generated by HyMeKo for {{config:robot_name}}.
//
// Mapping:
//   HyMeKo `link` decl   → SysML `part def Link` instance (`part <name> : Link`)
//   HyMeKo `*_joint`     → SysML `connection def`-typed connection
//   `+arc-ref`           → connection's first endpoint (parent link)
//   `-arc-ref`           → connection's second endpoint (child link)
//
// SysML 2 spec ref: https://github.com/Systems-Modeling/SysML-v2-Release
// (textual concrete syntax, ~2024 stable subset)

package {{config:robot_name}} {

    // ── Type definitions ──────────────────────────────────────────

    part def Link {
        attribute mass : Real;
    }

    part def FixedJoint {
        end parent : Link;
        end child  : Link;
    }

    part def RevoluteJoint {
        end parent : Link;
        end child  : Link;
        attribute axis : Vector3;
    }

    part def ContinuousJoint {
        end parent : Link;
        end child  : Link;
        attribute axis : Vector3;
    }

    part def PrismaticJoint {
        end parent : Link;
        end child  : Link;
        attribute axis : Vector3;
    }

    // ── Link instances ────────────────────────────────────────────
{{#each links}}
    part {{name}} : Link {
{{#if field:mass}}        :>> mass = {{field:mass}};
{{/if}}    }
{{/each}}

    // ── Joint connections ─────────────────────────────────────────
{{#each fixed_joints}}
    connection {{name}} : FixedJoint {
        end ::> {{bind:+:0}};
        end ::> {{bind:-:0}};
    }
{{/each}}
{{#each revolute_joints}}
    connection {{name}} : RevoluteJoint {
        end ::> {{bind:+:0}};
        end ::> {{bind:-:0}};
    }
{{/each}}
{{#each continuous_joints}}
    connection {{name}} : ContinuousJoint {
        end ::> {{bind:+:0}};
        end ::> {{bind:-:0}};
    }
{{/each}}
{{#each prismatic_joints}}
    connection {{name}} : PrismaticJoint {
        end ::> {{bind:+:0}};
        end ::> {{bind:-:0}};
    }
{{/each}}
}
