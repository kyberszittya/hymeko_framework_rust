// SysML v2 requirements model, generated by HyMeKo for {{config:robot_name}}.
//
// One signed-hypergraph IR projected to SysML v2: `requirement def` per
// requirement, `part def` per component (block), and the trace relations
// (satisfy / allocate / derive) from the signed hyperedges. Each binary trace
// edge is + realizer/derived, - requirement/source/block.
//
// SysML v2 spec ref: https://github.com/Systems-Modeling/SysML-v2-Release
// (textual concrete syntax, ~2024 stable subset).

package {{config:robot_name}} {

    // ── Requirements ──────────────────────────────────────────────
{{#each requirements}}
    requirement def {{name}} {
{{#if field:text}}        doc /* {{field:text}} */
{{/if}}    }
{{/each}}

    // ── Components ────────────────────────────────────────────────
{{#each blocks}}
    part def {{name}};
{{/each}}

    // ── Satisfy (component realizes requirement) ──────────────────
{{#each satisfies_edges}}
    satisfy {{bind:-:0}} by {{bind:+:0}};
{{/each}}

    // ── Allocate (requirement allocated to component) ─────────────
{{#each allocated_edges}}
    allocate {{bind:+:0}} to {{bind:-:0}};
{{/each}}

    // ── Derive (derived requirement ← source) — emitted as a «deriveReqt»
    //    connection, the structurally-faithful projection of the derives edge.
{{#each derives_edges}}
    connection def derive_{{name}} {
        // «deriveReqt» {{bind:+:0}} from {{bind:-:0}}
        end ::> {{bind:+:0}};
        end ::> {{bind:-:0}};
    }
{{/each}}
}
