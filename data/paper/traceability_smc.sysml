// SysML v2 requirements model, generated by HyMeKo for pick_place_cell.
//
// One signed-hypergraph IR projected to SysML v2: `requirement def` per
// requirement, `part def` per component (block), and the trace relations
// (satisfy / allocate / derive) from the signed hyperedges. Each binary trace
// edge is + realizer/derived, - requirement/source/block.
//
// SysML v2 spec ref: https://github.com/Systems-Modeling/SysML-v2-Release
// (textual concrete syntax, ~2024 stable subset).

package pick_place_cell {

    // ── Requirements ──────────────────────────────────────────────

    requirement def R1_safe_stop {
        doc /* Cell halts within 200 ms on E-stop. */
    }

    requirement def R2_pos_accuracy {
        doc /* End-effector positioning error <= 0.5 mm. */
    }

    requirement def R3_cycle_time {
        doc /* Pick-place cycle <= 4 s. */
    }

    requirement def R2a_repeatability {
        doc /* Repeatability <= 0.1 mm. */
    }


    // ── Components ────────────────────────────────────────────────

    part def SafetyController;

    part def MotionPlanner;

    part def Arm;

    part def Gripper;


    // ── Satisfy (component realizes requirement) ──────────────────

    satisfy R1_safe_stop by SafetyController;

    satisfy R2_pos_accuracy by MotionPlanner;

    satisfy R2_pos_accuracy by Arm;

    satisfy R3_cycle_time by MotionPlanner;

    satisfy R3_cycle_time by Gripper;


    // ── Allocate (requirement allocated to component) ─────────────

    allocate R2a_repeatability to Arm;


    // ── Derive (derived requirement ← source) — emitted as a «deriveReqt»
    //    connection, the structurally-faithful projection of the derives edge.

    connection def derive_der_rep {
        // «deriveReqt» R2a_repeatability from R2_pos_accuracy
        end ::> R2a_repeatability;
        end ::> R2_pos_accuracy;
    }

}
